#usage "silk_audit - report silkscreen text violations (height < 0.8 mm) on tPlace/bPlace."

// Collect every <text> on layer 21 (tPlace) or 22 (bPlace) in the board's
// <plain> section whose height is below the 0.8 mm silkscreen minimum, and
// dump them as one line per violation to silk_audit.txt in the current dir.
// Rows are sorted by (layer, x, y). No violations -> empty file.

string outpath = "silk_audit.txt";
real MIN_SIZE_MM = 0.8;

int   vcnt = 0;
int   vlayer[];
real  vx[];
real  vy[];
real  vsize[];
string vvalue[];

if (board) {
  board(B) {
    B.texts(T) {
      if (T.layer == 21 || T.layer == 22) {
        real sz_mm = u2mm(T.size);
        if (sz_mm < MIN_SIZE_MM) {
          vlayer[vcnt] = T.layer;
          vx[vcnt]     = u2mm(T.x);
          vy[vcnt]     = u2mm(T.y);
          vsize[vcnt]  = sz_mm;
          vvalue[vcnt] = T.value;
          vcnt++;
        }
      }
    }
  }
}

// Stable sort by (layer asc, x asc, y asc). vcnt is small; insertion sort.
int i, j;
for (i = 1; i < vcnt; i++) {
  int   kl = vlayer[i];
  real  kx = vx[i];
  real  ky = vy[i];
  real  ks = vsize[i];
  string kv = vvalue[i];
  j = i - 1;
  while (j >= 0) {
    int swap = 0;
    if (vlayer[j] > kl) swap = 1;
    else if (vlayer[j] == kl && vx[j] > kx) swap = 1;
    else if (vlayer[j] == kl && vx[j] == kx && vy[j] > ky) swap = 1;
    if (!swap) break;
    vlayer[j + 1] = vlayer[j];
    vx[j + 1]     = vx[j];
    vy[j + 1]     = vy[j];
    vsize[j + 1]  = vsize[j];
    vvalue[j + 1] = vvalue[j];
    j--;
  }
  vlayer[j + 1] = kl;
  vx[j + 1]     = kx;
  vy[j + 1]     = ky;
  vsize[j + 1]  = ks;
  vvalue[j + 1] = kv;
}

output(outpath, "wt") {
  for (int k = 0; k < vcnt; k++) {
    string lname = (vlayer[k] == 21) ? "tPlace" : "bPlace";
    printf("text=\"%s\" x=%.3f y=%.3f size=%.3f layer=%s\n",
           vvalue[k], vx[k], vy[k], vsize[k], lname);
  }
}

exit(0);
